# firmware_requirements_doc

## 1: Operational requirement (Functional)

### 1.1: Robot behavior (Functional)

#### 1.1.1: Start robot (Functional)
หุ่นยนต์จะเริ่มทำงาน เมื่อกดปุ่มเพิ่มเริ่มการทำงาน

#### 1.1.2: restart system at maximum time 1 minute (Functional)
ระบบต้องเริ่มต้นใหม่ทั้งหมดภายใน 1 นาที

#### 1.1.3: Manipulator home position (Functional)
แขนกลเคลื่อนที่สู่ตำแหน่ง Home position

#### 1.1.4: reset mobile robot’s parameter (Functional)
รีเช็ตค่าการเคลื่อนที่ทั้งหมด ของ mobile robot

### 1.2: Hardware (Functional)

#### 1.2.1: Mobile Robot Position (Functional)
ค่าตำแหน่งการเคลื่อนที่ของ mobile robot

#### 1.2.2: Mobile Robot Velocity (Functional)
ค่าความเร็วของ mobile robot

#### 1.2.3: Mobile Robot Acceleration (Functional)
ค่าความเร่งของ mobile robot

#### 1.2.4: Manipulator Position (Functional)
ค่าตำแหน่งการเคลื่อนที่ของ Manipulator

#### 1.2.5: Manipulator Velocity (Functional)
ค่าความเร็วของ Manipulator

#### 1.2.6: Manipulator Acceleration (Functional)
ค่าความเร่งของ Manipulator

#### 1.2.7: Enable Gripper (Functional)
สถานะการสั่งงานตัวหยิบจับ

## 2: Robot Monitoring (Functional)

### 2.1: Electronics (Functional)

#### 2.1.1: System Current (Sys_Amp) (Functional)
หุ่นยนต์จะสามารถแสดงค่ากระแสไฟฟ้าทั้งหมดของระบบ
- Rationale: แสดงผลการใช้กระแสไฟฟ้าของหุ่นยนต์

##### 2.1.1.1: Current Sensor Interface (Functional)
หุ่นยนต์สามารถ interface ค่าจาก current sensor
- Rationale: เพื่อนำค่าที่ได้ไปเก็บไว้ในตัวแปร Sys_Amp

#### 2.1.2: System Voltage (Sys_Volt) (Functional)
หุ่นยนต์จะสามารถแสดงค่าแรงดันไฟฟ้าทั้งหมดของระบบ
- Rationale: แสดงผลของระดับแรงดันที่แบตเตอรี่จ่ายไปที่โหลด ณ ระดับกระแสใดๆ

##### 2.1.2.1: Voltage Sensor Interface (Functional)
หุ่นยนต์ระสามารถ interface ค่าจาก voltage sensor
- Rationale: เพื่อนำค่าที่ได้ไปเก็บไว้ในตัวแปร Sys_Volt

#### 2.1.3: Battery Temperature (Batt_Temp) (Functional)
หุ่นยนต์จะสามารถแสดงค่าอุณหภูมิของแบตเตอรี่
- Rationale: แสดงอุณหภูมิโดยรวมของแบตเตอรี่

##### 2.1.3.1: Temperature Sensor Interface (Functional)
หุ่นยนต์สามารถ interface ค่าจาก Temperature Sensor
- Rationale: เพื่อนำค่าที่ได้ไปเก็บไว้ในตัวแปร Batt_Temp

#### 2.1.4: Battery Level (Batt_Level) (Functional)
หุ่นยนต์จะสามารถแสดงค่าระดับพลังงานของแบตเตอรี่
- Rationale: แสดงระดับประจุคงเหลือของแบตเตอรี่ ณ เวลานั้น

##### 2.1.4.1: State of Charge Estimation (Functional)
หุ่นยนต์สามารถนำค่าแรงดันไฟฟ้า และ กระแสไฟฟ้า มาทำการประมาณค่า SOC (State of Charge)
- Rationale: เพื่อบอกระดับประจุของแหล่งจ่ายเมื่อเทียบกับประจุ ณ ตอนเริ่มใช้งาน

## 3: Safety requirements (Functional)

### 3.1: Internal Power Limitation (IPL) (Functional)

#### 3.1.1: System Over-Current (Over_Amp_Stat) (Functional)
หุ่นยนต์สามารถรับสัญญาณแจ้งเตือนกระแสไฟฟ้าเกินกำหนดจากวงจรอิเล็กทรอนิกส์
- Rationale: เพื่อป้องกันความเสียหายของเเหล่งจ่ายไฟเนื่องจากการลัดวงจรหรือการใช้งานเกินกระเเสพิกัดของระบบ

#### 3.1.2: System Under Voltage (Under_Volt_Stat) (Functional)
หุ่นยนต์สามารถรับสัญญาณแจ้งเตือนเมื่อแรงดันของแหล่งจ่ายต่ำเกินกำหนดจากวงจรอิเล็กทรอนิกส์
- Rationale: เพื่อป้องกันความเสียหายของเเบตเตอรี่จากการ Over Discharge

#### 3.1.3: Maximum System Voltage (Over_Volt_Stat) (Functional)
หุ่นยนต์สามารถรับสัญญาณแจ้งเตือนเมื่อแรงดันของแหล่งจ่ายมากเกินกำหนดจากวงจรอิเล็กทรอนิกส์
- Rationale: เพื่อป้องกันความเสียหายของอุปกรณ์ไฟฟ้าต่างๆ จากความต่างศักย์ที่มากเกินกว่าที่กำหนด

#### 3.1.4: System Over Temperature (Over_Temp_Stat) (Functional)
หุ่นยนต์สามารถรับสัญญาณแจ้งเตือนอุณหภูมิเกินกำหนดจากวงจรอิเล็กทรอนิกส์
- Rationale: ป้องกันอันตรายที่เกิดขึ้นกับแหล่งจ่าย

### 3.2: Rechargeabilty (Functional)

#### 3.2.1: Battery Charge Time (Batt_Charge_Time) (Functional)
เเบตเตอรี่ต้องสามารถชาร์ตเเบตเตอรี่จาก 0-100% (SOC) ได้ภายในระยะเวลาที่กำหนด
- Rationale: เพื่อให้หุ่นยนต์พร้อมใช้งานได้ทันทีภายในระยะเวลาที่กำหนด

#### 3.2.2: Battery Over Temperature while Charging (Batt_Charge_Over_Temp) (Functional)
อุณหภูมิของเเบตเตอรี่ขณะทำการชาร์ตสูงเกินค่าที่กำหนดจากการอ่านค่าของ Temperature Sensor
- Rationale: ใช้หยุดทำการชาร์ตเเบตเตอรี่เมื่ออุณหภูมิขณะชาร์ตเเบตเตอรี่สูงเกินค่าที่กำหนด

#### 3.2.3: Battery Low Level (Batt_Low_Stat) (Functional)
ระดับพลังงานของเเบตเตอรี่ต่ำกว่าค่าที่กำหนด
- Rationale: ระบบจัดการพลังงานมีข้อมูลในการสั่งให้หุ่นยนต์กลับไปชาร์จเเบต

#### 3.2.4: Start to Charge at the Charging Station (Batt_Charging_Stat) (Functional)
เริ่มต้นการชาร์จเเบตเตอรี่ที่จุดชาร์จ
- Rationale: หุ่นยนต์สามารถชาร์จพลังงานตัวเองได้อัตโนมัติ

#### 3.2.5: Stop to Charge at the Charging Station (Batt_Charging_Stat) (Functional)
หยุดการชาร์ตเเบตเตอรี่เมื่อทำการชาร์จแบตเตอรี่จนประจุเต็ม
- Rationale: ป้องกันไม่ให้แบตเตอรี่ Overcharge ตัวเอง

### 3.3: Emergency Trigger Behavior (Functional)

#### 3.3.1: Environment Temperature Warning (both over and under) (Functional)

##### 3.3.1.1: Over Temperature Level (Functional)
เมื่ออุณหภูมิสภาพเเวดล้อมเกินอุณหภูมิที่กำหนดไว้ ระบบจะมีการเตือน

##### 3.3.1.2: Under Temperature Level (Functional)
เมื่ออุณหภูมิสภาพเเวดล้อมต่ำกว่าอุณหภูมิที่กำหนดไว้ ระบบจะมีการเตือน

##### 3.3.1.3: Normal Operating Temperature Level (Functional)
เมื่ออุณหภูมิสภาพเเวดล้อมอยู่ในช่วงที่กำหนด สถานะเตือนอุณหภูมิจะกลับมามี สถาณะเดิม หรือ false

#### 3.3.2: Collision Detection (Functional)

##### 3.3.2.1: Collision Warning (Functional)
เมื่อหุ่นยนต์พบเจอสิ่งกีดขวางผ่านเซ็นเซอร์ ระบบจะส่งคำเตือนการเจอสิ่งกีดขวางไปยังระบบนำทางเพื่อประมวลผลเส้นทางใหม่

##### 3.3.2.2: Collision Acknowledging (Functional)
เมื่อระบบนำทางได้ตอบสนองกลับมาคำเตือนการเจอสิ่งกีดขวางจะกลับสู่สถาณะเดิม หรือ false

#### 3.3.3: Embedded devices status (Functional)

##### 3.3.3.1: Electronic Devices Timeout (Functional)
เมื่อหุ่นยนต์พบว่ามีอุปกรณ์ที่หยุดการทำงาน (ไม่ส่งสถาณะกลับมาที่ระบบเฝ้าระวัง) หุ่นยนต์จะมีการเตือนสถาณะอุปกรณ์เพื่อให้ระบบเข้าสู้สถานะฉุกเฉินได้(Device_Fail_Stat = true) และส่งคำสั่งเริ่มต้นใหม่ไปยังอุปกรณ์

##### 3.3.3.2: Electronic Devices Resuming (Functional)
เมื่ออุปกรณ์กลับมาทำงานการเตือนสถาณะอุปกรณ์จะกลับมาเหมือนสถาณะเริ่มต้นหรือ false

#### 3.3.4: Power Distribution. (Functional)

##### 3.3.4.1: Enabling Every Electronic Power (Except Actuator) (Functional)
เมื่อหุ่นยนต์ไม่ถูกปิดจากสวิตซ์จะทำให้อุปกรณ์ได้รับพลังงานไฟฟ้า

##### 3.3.4.2: Disabling Every Electronic Power (Functional)
เมื่อหุ่นยนต์ถูกปิดจากสวิตซ์จะทำให้อุปกรณ์ไม่ได้รับพลังงานไฟฟ้า

##### 3.3.4.3: Enabling Actuator Power (Functional)
เมื่อหุ่นยนต์ไม่มีสถานะฉุกเฉินหุ่นยนต์หรือเกิดการเปิดสวิตซ์จะมีการเปิดระบบขับเคลื่อน

##### 3.3.4.4: Disabling Actuator Power (Functional)
เมื่อหุ่นยนต์ได้รับสถานะฉุกเฉินหุ่นยนต์หรือเกิดการปิดสวิตซ์จะมีการตัดพลังงานระบบขับเคลื่อน

#### 3.3.5: Resume Behavior (Functional)
เมื่อหุ่นยนต์ไม่มีสถานะฉุกเฉินหุ่นยนต์ หุ่นยนต์จะกลับมาอยู่ในสถานะทำงาน และส่งสัญญาณไปยังระบบประมวลผลเพื่อให้ส่งคำสั่งเพื่อกลับสู่สถานะรอคำสั่ง
