# requirement set

## 2.0: Movability (Functional)
ส่วนการเคลื่อนที่

### 2.1: มีการรับส่งข้อมูลเกี่ยวกับตำแหน่งของหุ่นยนต์ (Functional)
มีการรับส่งข้อมูลเกี่ยวกับตำแหน่งการเคลื่อนที่
- Rationale: หุ่นยนต์ไปยังที่หมายได้ตามคำสั่ง

#### 2.1.1: ความคลาดเคลื่อน (Functional)
ตำแหน่งความคลาดเคลื่อนได้ไม่เกิน …… mm.
- Rationale: อุปกรณ์ที่เลือกใช้จะได้ไม่แพงเกินไปแต่ยังทำงานได้

#### 2.1.2: หุ่นยนต์สามารถรับรู้ตำแหน่งของตนเอง (Functional)
มีการรับส่งข้อมูลตำแหน่งของตนเองกลับไปประมวลผลได้
- Rationale: เพื่อช่วยพิจารณาคำสั่งต่อไปของหุ่นยนต์

### 2.2: มีการรับส่งข้อมูลเกี่ยวกับความเร็วของหุ่นยนต์ (Functional)

#### 2.2.1: ความเร็วที่หุ่นยนต์ทำได้ (Functional)
ความเร็วในการเคลื่อนที่สูงสุดของหุ่นยนต์ต้องไม่ต่ำกว่า …m/s
- Rationale: เพื่อให้ทำงานที่กำหนดได้ทันเวลา และรู้ขอบเขตในการเลือกอุปกรณ์ขับเคลื่อน

### 2.3: มีการรับส่งข้อมูลเกี่ยวกับความเร่งของหุ่นยนต์ (Functional)

#### 2.3.1: ความเร่งที่หุ่นยนต์ทำได้ (Functional)
ความเร่งในการเคลื่อนที่สูงสุดของหุ่นยนต์ต้องไม่ต่ำกว่า …m/s^2
- Rationale: เพื่อให้ทำงานที่กำหนดได้ทันเวลา และรู้ขอบเขตในการเลือกอุปกรณ์ขับเคลื่อน

## 3.0: Manipulator (Functional)
ส่วนของการยกของ

### 3.1: แขนกลสามารถหยิบจับวัตถุที่สั่งได้ (Functional)

#### 3.1.1: แขนกลสามารถตรวจสอบตำแหน่งที่วัตถุวางอยู่ได้ (Functional)
- Rationale: แขนกลหยิบของไม่ผิดชิ้น

#### 3.1.2: แขนกลสามารถตรวจสอบได้ว่าหยิบวัตถุสำเร็จแล้ว (Functional)
แขนกลรับรู้ได้ว่าหยิบวัตถุที่สั่งได้แล้ว
- Rationale: แขนกลรอทำงานหยิบของเสร็จก่อนโดยไม่โดนคำสั่งอื่นขัดหรือหยิบใหม่ถ้าหยิบพลาด
